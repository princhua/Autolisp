;选择集
(defun c:ttt ( )
	(setq p1(getpoint"choose first point"))
	(setq p2(getcorner p1"choose last point"))
	(setq ax (car p1))
	(setq bx (car p2))
	(if (< ax bx) 
		(setq ss(ssget "w" p1 p2))
		(setq ss(ssget "c" p1 p2))
	)
	(setq dia(getint"\n input offset distance <25>"))
	(if(= dia nil)(setq dia 25))	
	(setq a 0)
	; (initget "i I C c")
	; (setq mode(getkword"contact<c>inscribe<i>:default<c>:"))
;(setq mode(getstring"contact<c>inscribe<i>:default<c>"))
	;(if(= mode nil)(setq mode "c"))
	(repeat (sslength ss)
		(setq ent (ssname ss a))
		(setq ent_data (entget ent))
		(setq ent_type(cdr(assoc 0 ent_data)))
		(if(= ent_type "CIRCLE")
			(progn
				(setq old_r (cdr (assoc 40 ent_data)))
				(setq base_point(cdr(assoc 10 ent_data)))
				(command "circle" base_point (+ old_r dia) )
			)
		)
	(setq a(+ a 1))
	)
  (command "erase" ss "")
)
