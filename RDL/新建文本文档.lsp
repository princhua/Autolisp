(defun c:ttt ()
	(setq dlg_id(load_dialog "C:\\Users\\chenggh\\Desktop\\lisp\\截面图\\截面图DCL"))
	(if(< dlg_id 0) (exit))
	(if (not(new_dialog "section" dlg_id))(exit))
	(setq origin '(0 0))
	
	(setq depth1 90 depth2 30 trench_1 70 trench_2 70 pad_dis1 150 pad_dis2 150 ang1 60 ang2 65)
	(setdata)
	(action_tile "accept" "(getdata)(done_dialog 1)")
	(action_tile "cancel" "(done_dialog 0)")
	(setq std (start_dialog))
	(unload_dialog dlg_id)
	(if (= std 1)
		(progn
			(MVP_section_drawing)
		)
	)
	(command "zoom" "e")
	(princ)
)

(defun getdata()
	(setq depth1(atof(get_tile "depth1")))
	(setq depth2(atof(get_tile "depth2")))
	(setq st(atof(get_tile "st")))
	(setq cv(atof(get_tile "cv")))
	(setq trench_1(atof(get_tile "trench_dis1")))
	(setq trench_2(atof(get_tile "trench_dis2")))
	(setq pad_dis1(atof(get_tile "pad_dis1")))
	(setq pad_dis2(atof(get_tile "pad_dis2")))
	(setq ang1(get_tile "ang1"))
	(setq ang2(get_tile "ang2"))

)

(defun setdata()
	(set_tile "depth1"(rtos depth1 2 2))
	(set_tile "depth2"(rtos depth2 2 2))
	(set_tile "trench_dis1"(rtos trench_1 2 2))
	(set_tile "trench_dis2"(rtos trench_2 2 2))
	(set_tile "pad_dis1"(rtos pad_dis1 2 2))
	(set_tile "pad_dis2"(rtos pad_dis2 2 2))
	(set_tile "ang1"(rtos ang1 2 2))
	(set_tile "ang2"(rtos ang2 2 2))
)

(defun MVP_section_drawing()
	(setq apt7 (list (- 25) (+ depth1 depth2)))
	(setq apt1 (list -25 depth2) apt2 (list -225 depth2) pad_c (list (- pad_dis1) 0))
	(setq pt1 '(-25 0) pt2 (polar pad_c 0 27.5) pt3 (polar pad_c (- pi) 27.5) pt4 (list (-(- pad_dis1)  trench_1) depth2) 
	pt5 (polar apt7 pi 800) 
	)
	(setq apt3 (polar pt1 (- pi (angtof ang2)) 50))
	(setq apt4 (polar pt2  (angtof ang2) 50))
	(setq apt5 (polar pt3 (- pi (angtof ang2)) 50))
	(setq apt6 (polar pt4 (- pi (angtof ang1)) 200))
	(command "line" apt1 apt2 "")
	(setq e1 (entlast))
	(command "line" apt7 pt5 "")
	(setq e2 (entlast))
	(command "pline" pt1 apt3 apt4 pt2 pt3 apt5 pt4 apt6 pt5 "")
	(setq e3 (entlast))
	;(command "trim" e1 e2 e3 "" apt1 apt3 apt4 (polar pad_c (* pi 0.5) depth2) apt5 apt2 apt6 apt7 )
)
