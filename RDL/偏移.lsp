(defun c:ottt ( )
	(setq p1(getpoint"choose first point"))
	(setq p2(getcorner p1"choose last point"))
	(setq ax (car p1))
	(setq bx (car p2))
	(setq mode "c")
	(if (< ax bx) 
	(setq ss(ssget "w" p1 p2))
	(setq ss(ssget "c" p1 p2))
	)
;(setq ss (ssget))
	(setq off_dis(getreal"\n input distance of RDL to be altered<15>:"))
	(if (= off_dis nil) (setq off_dis 15))
	(setq n 0)
	(repeat (sslength ss)
		(setq ent (ssname ss n))
		(setq ent_data (entget ent))
		(setq ent_type(cdr(assoc 0 ent_data)))
		(if(= ent_type "CIRCLE")
			(progn
				(setq old_r (cdr (assoc 40 ent_data)))
				(setq new_r (* old_r  rate))
				(setq ent_data(subst (cons 40 new_r) (assoc 40 ent_data) ent_data))
				(entmod ent_data)
			)
		)
	(setq n(+ n 1))
	)
)
